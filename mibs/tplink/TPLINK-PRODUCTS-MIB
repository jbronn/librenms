TPLINK-PRODUCTS-MIB DEFINITIONS ::= BEGIN
	IMPORTS
        MODULE-IDENTITY
                FROM SNMPv2-SMI
		tplinkProducts
				FROM TPLINK-MIB;

		
	tplink-tlsl5428		OBJECT IDENTIFIER ::= { tplinkProducts 1 }
	tplink-tlsl3452		OBJECT IDENTIFIER ::= { tplinkProducts 2 }
	tplink-tlsg3424		OBJECT IDENTIFIER ::= { tplinkProducts 3 }
	tplink-tlsg3216		OBJECT IDENTIFIER ::= { tplinkProducts 4 }
	tplink-tlsg3210		OBJECT IDENTIFIER ::= { tplinkProducts 5 }
	tplink-tlsl3428		OBJECT IDENTIFIER ::= { tplinkProducts 6 }
	tplink-tlsg5428		OBJECT IDENTIFIER ::= { tplinkProducts 7 }
	tplink-tlsg3424p	OBJECT IDENTIFIER ::= { tplinkProducts 8 }
	tplink-tlsg5412f	OBJECT IDENTIFIER ::= { tplinkProducts 9 }
	tplink-t2700-28tct	OBJECT IDENTIFIER ::= { tplinkProducts 10 }
	tplink-tlsl2428		OBJECT IDENTIFIER ::= { tplinkProducts 11 }
	tplink-tlsg2216		OBJECT IDENTIFIER ::= { tplinkProducts 12 }
	tplink-tlsg2424		OBJECT IDENTIFIER ::= { tplinkProducts 13 }
	tplink-tlsg5428cn	OBJECT IDENTIFIER ::= { tplinkProducts 14 }
	tplink-tlsg2452	 	OBJECT IDENTIFIER ::= { tplinkProducts 15 }
	tplink-tlsl2218		OBJECT IDENTIFIER ::= { tplinkProducts 16 }
	tplink-tlsg2424p	OBJECT IDENTIFIER ::= { tplinkProducts 17 }
	tplink-tlsg2210		OBJECT IDENTIFIER ::= { tplinkProducts 18 }
	tplink-tlsl2210		OBJECT IDENTIFIER ::= { tplinkProducts 19 }
	tplink-t3700g-28tq	OBJECT IDENTIFIER ::= { tplinkProducts 20 }
	tplink-tlsl2226p	OBJECT IDENTIFIER ::= { tplinkProducts 21 }
	tplink-tlsl2452		OBJECT IDENTIFIER ::= { tplinkProducts 22 }
	tplink-tlsl2218p	OBJECT IDENTIFIER ::= { tplinkProducts 23 }
	tplink-tlsg3424-ipv6	OBJECT IDENTIFIER ::= { tplinkProducts 24 }
	tplink-tlsg2008		OBJECT IDENTIFIER ::= { tplinkProducts 25 }
	tplink-tlsg2210p	OBJECT IDENTIFIER ::= { tplinkProducts 26 }
	tplink-t2700g-28tq	OBJECT IDENTIFIER ::= { tplinkProducts 27 }
	tplink-t1600g-28ts	OBJECT IDENTIFIER ::= { tplinkProducts 28 }
	tplink-t1600g-52ts	OBJECT IDENTIFIER ::= { tplinkProducts 29 }
	tplink-t3700g-54tq	OBJECT IDENTIFIER ::= { tplinkProducts 30 }
	tplink-t1700g-28tq	OBJECT IDENTIFIER ::= { tplinkProducts 31 }
	tplink-t1700g-52tq	OBJECT IDENTIFIER ::= { tplinkProducts 32 }
	tplink-t2600g-28ts	OBJECT IDENTIFIER ::= { tplinkProducts 33 }
	tplink-t2600g-52ts	OBJECT IDENTIFIER ::= { tplinkProducts 34 }
	tplink-t1600g-28ps	OBJECT IDENTIFIER ::= { tplinkProducts 37 }
	tplink-t1600g-52ps	OBJECT IDENTIFIER ::= { tplinkProducts 38 }
	tplink-tlsg2224p	OBJECT IDENTIFIER ::= { tplinkProducts 39 }
	tplink-tlsg3428 	OBJECT IDENTIFIER ::= { tplinkProducts 40 }
	tplink-t1700x-16ts	OBJECT IDENTIFIER ::= { tplinkProducts 41 }
	-- tlsl3226p-combo_v1  OBJECT IDENTIFIER ::= { l2manageswitch 42 }
	-- tlsl3218pe-combo_v1 OBJECT IDENTIFIER ::= { l2manageswitch 43 }
	tplink-t2500-28tc   OBJECT IDENTIFIER ::= { tplinkProducts 44 }
	-- tlsl3226pe-combo_v1 OBJECT IDENTIFIER ::= { l2manageswitch 45 }
	-- tlsl3452-combo_v1   OBJECT IDENTIFIER ::= { l2manageswitch 46 }
	-- tlsg3210_v3         OBJECT IDENTIFIER ::= { l2manageswitch 47 }
	-- tlsg3218_v1         OBJECT IDENTIFIER ::= { l2manageswitch 48 }
	-- tlsl3226-combo_v1   OBJECT IDENTIFIER ::= { l2manageswitch 49 }
	-- tlsl3226_v1         OBJECT IDENTIFIER ::= { l2manageswitch 50 }
	-- tlsg3452_v1         OBJECT IDENTIFIER ::= { l2manageswitch 51 }
	-- tlsg5428_v2         OBJECT IDENTIFIER ::= { l3manageswitch 52 }
	-- tlsl3428-combo_v1   OBJECT IDENTIFIER ::= { l2manageswitch 53 }
	-- tlsl3218_v1         OBJECT IDENTIFIER ::= { l2manageswitch 54 }
	-- tlsl3218-combo_v1   OBJECT IDENTIFIER ::= { l2manageswitch 55 }
	-- tlsg3226p_v1        OBJECT IDENTIFIER ::= { l2manageswitch 56 }
	-- tlsg3226pe_v1       OBJECT IDENTIFIER ::= { l2manageswitch 57 }
	-- tlsg3218pe_v1       OBJECT IDENTIFIER ::= { l2manageswitch 58 }
	tplink-t2500g-10ts  OBJECT IDENTIFIER ::= { tplinkProducts 59 }
	-- tlsl3210_v2         OBJECT IDENTIFIER ::= { l2manageswitch 60 }
	-- tlsl3109_v1         OBJECT IDENTIFIER ::= { l2manageswitch 61 }
	-- tlsl3210pe_v1       OBJECT IDENTIFIER ::= { l2manageswitch 62 }
	-- tlsg3210pe_v1       OBJECT IDENTIFIER ::= { l2manageswitch 63 }
	-- tlsl5218-combo_v1   OBJECT IDENTIFIER ::= { l3manageswitch 64 }
	-- tlsl5210_v1	        OBJECT IDENTIFIER ::= { l3manageswitch 65 }
	-- tlsl5428-combo_v1	OBJECT IDENTIFIER ::= { l3manageswitch 66 }
	-- tlsg5218_v1	        OBJECT IDENTIFIER ::= { l3manageswitch 67 }
	-- tlsg5210_v1	        OBJECT IDENTIFIER ::= { l3manageswitch 68 }
	-- tlsl5452-combo_v1	OBJECT IDENTIFIER ::= { l3manageswitch 71 }
	tplink-t2600g-18ts	OBJECT IDENTIFIER ::= { tplinkProducts 72 }
	-- tlsg5452_v1	        OBJECT IDENTIFIER ::= { l3manageswitch 73 }
	tplink-t2600g-28mps	OBJECT IDENTIFIER ::= { tplinkProducts 74 }
	-- tlsg5820f_v1        OBJECT IDENTIFIER ::= { l3manageswitch 75 }
	tplink-t1500g-8t	OBJECT IDENTIFIER ::= { tplinkProducts 76 }
	tplink-t1500g-10ps	OBJECT IDENTIFIER ::= { tplinkProducts 78 }
	tplink-t1500g-10mps	OBJECT IDENTIFIER ::= { tplinkProducts 80 }
	tplink-t1500-28tc	OBJECT IDENTIFIER ::= { tplinkProducts 82 }
	tplink-t1500-28pct	OBJECT IDENTIFIER ::= { tplinkProducts 84 }
	tplink-t1600g-18ts	OBJECT IDENTIFIER ::= { tplinkProducts 86 }
	tplink-t2500g-10mps	OBJECT IDENTIFIER ::= { tplinkProducts 88 }
	tplink-t2600g-28ps	OBJECT IDENTIFIER ::= { tplinkProducts 90 }
	tplink-t2600g-28sq	OBJECT IDENTIFIER ::= { tplinkProducts 92 }
	tplink-tlsg2008p	OBJECT IDENTIFIER ::= { tplinkProducts 94 }
	tplink-tlsg2210mp	OBJECT IDENTIFIER ::= { tplinkProducts 96 }
	tplink-tlsg2428p	OBJECT IDENTIFIER ::= { tplinkProducts 98 }
	tplink-tlsl2428p	OBJECT IDENTIFIER ::= { tplinkProducts 100 }
	tplink-tlsg3428xmp	OBJECT IDENTIFIER ::= { tplinkProducts 102 }
	tplink-tlsg3210xhp-m2	OBJECT IDENTIFIER ::= { tplinkProducts 104 }
	tplink-tlsg3428x	OBJECT IDENTIFIER ::= { tplinkProducts 106 }
	tplink-tlsg3428x-dc	OBJECT IDENTIFIER ::= { tplinkProducts 108 }
	tplink-tlsx3016f	OBJECT IDENTIFIER ::= { tplinkProducts 110 }
	tplink-tlsg3428mp		OBJECT IDENTIFIER ::= { tplinkProducts 112 }
	tplink-tlsg3452		OBJECT IDENTIFIER ::= { tplinkProducts 114 }
	tplink-tlsg2218		OBJECT IDENTIFIER ::= { tplinkProducts 116 }
	tplink-t2700g-28tq-dc		OBJECT IDENTIFIER ::= { tplinkProducts 118 }
	tplink-tlsx3008f		OBJECT IDENTIFIER ::= { tplinkProducts 120 }
	tplink-tlsg3428-v2		OBJECT IDENTIFIER ::= { tplinkProducts 122 }
	tplink-t2700g-28tq-v4		OBJECT IDENTIFIER ::= { tplinkProducts 122 }
	tplink-tlsx3206hpp		OBJECT IDENTIFIER ::= { tplinkProducts 126 }
	tplink-tlsg3428mp-v2		OBJECT IDENTIFIER ::= { tplinkProducts 128 }
	tplink-tlsg2210p-v4	OBJECT IDENTIFIER ::= { tplinkProducts 130 }
	tplink-tlsg2008p-v2	OBJECT IDENTIFIER ::= { tplinkProducts 132 }
	tplink-tlsg2008-v4		OBJECT IDENTIFIER ::= { tplinkProducts 134 }
	tplink-tlsg2428p-v2		OBJECT IDENTIFIER ::= { tplinkProducts 136 }
	tplink-tlsg2210mp-v2	OBJECT IDENTIFIER ::= { tplinkProducts 138 }
	tplink-tlsg3452p-v2		OBJECT IDENTIFIER ::= { tplinkProducts 140 }
	tplink-tlsg3428mp-v3		OBJECT IDENTIFIER ::= { tplinkProducts 142 }
	tplink-tlsg2428p-v4		OBJECT IDENTIFIER ::= { tplinkProducts 144 }
	tplink-tlsg3428mp-v4		OBJECT IDENTIFIER ::= { tplinkProducts 146 }
	tplink-tlsg3452x		OBJECT IDENTIFIER ::= { tplinkProducts 148 }
	tplink-tlsg3452xp		OBJECT IDENTIFIER ::= { tplinkProducts 150 }
	tplink-tlsl2428p-v5		OBJECT IDENTIFIER ::= { tplinkProducts 152 }
	tplink-tlsg2008p-v3	OBJECT IDENTIFIER ::= { tplinkProducts 154 }
	tplink-tlsg2210mp-v3	OBJECT IDENTIFIER ::= { tplinkProducts 156 }
	tplink-tlsg2210p-v5	OBJECT IDENTIFIER ::= { tplinkProducts 158 }
	tplink-tlsg3452p-v3		OBJECT IDENTIFIER ::= { tplinkProducts 160 }
	tplink-tlsg2428p-v5		OBJECT IDENTIFIER ::= { tplinkProducts 162 }
	tplink-tlsg3428xmp-v2		OBJECT IDENTIFIER ::= { tplinkProducts 164 }
	tplink-tlsg3428mp-v5		OBJECT IDENTIFIER ::= { tplinkProducts 166 }
	tplink-tlsl2428p-v6		OBJECT IDENTIFIER ::= { tplinkProducts 168 }
	tplink-tlsg3428x-ups		OBJECT IDENTIFIER ::= { tplinkProducts 170 }
	tplink-tlsg3428xf		OBJECT IDENTIFIER ::= { tplinkProducts 172 }
	tplink-tlsg3210xhp-m2-v2		OBJECT IDENTIFIER ::= { tplinkProducts 174 }
	tplink-tlsg2428p-v3		OBJECT IDENTIFIER ::= { tplinkProducts 176 }
	tplink-tlsg3452p-v320		OBJECT IDENTIFIER ::= { tplinkProducts 178 }
	tplink-tlsg2210mp-v4	OBJECT IDENTIFIER ::= { tplinkProducts 180 }
	tplink-tlsg3452xp-v2		OBJECT IDENTIFIER ::= { tplinkProducts 182 }
	tplink-tlsg3428xmp-v3		OBJECT IDENTIFIER ::= { tplinkProducts 184 }
	tplink-tlsg3428mp-v6		OBJECT IDENTIFIER ::= { tplinkProducts 186 }
	tplink-tlsg2016p		OBJECT IDENTIFIER ::= { tplinkProducts 188 }	
	tplink-tlsg2218p		OBJECT IDENTIFIER ::= { tplinkProducts 190 }
	tplink-sg3428xpp-m2        OBJECT IDENTIFIER ::= { tplinkProducts 192 }
    tplink-tlsgs6500-24g4xf      OBJECT IDENTIFIER ::= { tplinkProducts 194 }
    tplink-tlsg6428xhp-v1  OBJECT IDENTIFIER ::= { tplinkProducts 196 }
    tplink-tlsg6654x-v1      OBJECT IDENTIFIER ::= { tplinkProducts 198 }
    tplink-tlsg6654xhp-v1  OBJECT IDENTIFIER ::= { tplinkProducts 200 }
    tplink-tlsg6428y-m2-v1      OBJECT IDENTIFIER ::= { tplinkProducts 202 }
    tplink-tlsg6654y-m2-v1      OBJECT IDENTIFIER ::= { tplinkProducts 204 }
    tplink-sg3428x-m2 OBJECT IDENTIFIER ::= { tplinkProducts 206 }
    tplink-sg2005p-pd OBJECT IDENTIFIER ::= { tplinkProducts 208 }
    tplink-tlsg3210xhp-m2-v3 OBJECT IDENTIFIER ::= { tplinkProducts 210 }
    tplink-tlsg728p OBJECT IDENTIFIER ::= { tplinkProducts 212 }
    tplink-tlsg3210x-m2 OBJECT IDENTIFIER ::= { tplinkProducts 214 }
    tplink-tlsg3218xp-m2 OBJECT IDENTIFIER ::= { tplinkProducts 216 }
	tplink-s4500-8gp OBJECT IDENTIFIER ::= { tplinkProducts 218 }
	tplink-s5500-24gp4f OBJECT IDENTIFIER ::= { tplinkProducts 220 }
	tplink-s5500-48gp4f OBJECT IDENTIFIER ::= { tplinkProducts 222 }
	tplink-s4500-8gp2f OBJECT IDENTIFIER ::= { tplinkProducts 224 }
	tplink-s4500-8g OBJECT IDENTIFIER ::= { tplinkProducts 226 }
	tplink-s5500-24f4xf OBJECT IDENTIFIER ::= { tplinkProducts 228 }
	tplink-s5500-16xf OBJECT IDENTIFIER ::= { tplinkProducts 230 }
	tplink-s5500-8xf OBJECT IDENTIFIER ::= { tplinkProducts 232 }
	tplink-s5500-48gp4xf OBJECT IDENTIFIER ::= { tplinkProducts 234 }
	tplink-s5500-8mhp2xf OBJECT IDENTIFIER ::= { tplinkProducts 236 }
	tplink-s4500-16gp OBJECT IDENTIFIER ::= { tplinkProducts 238 }
	tplink-s4500-16g2f OBJECT IDENTIFIER ::= { tplinkProducts 240 }
	tplink-sg2210xmp-m2 OBJECT IDENTIFIER ::= { tplinkProducts 242 }
	tplink-s5500-24gp4xf OBJECT IDENTIFIER ::= { tplinkProducts 244 }
	tplink-s5500-24mpp4xf OBJECT IDENTIFIER ::= { tplinkProducts 246 }
	tplink-s4500-8ghp2f OBJECT IDENTIFIER ::= { tplinkProducts 248 } 
	tplink-s5500-4xhpp2xf OBJECT IDENTIFIER ::= { tplinkProducts 250 } 
	tplink-sx6632yf-v1 OBJECT IDENTIFIER ::= { tplinkProducts 252 }
	tplink-sx3032f OBJECT IDENTIFIER ::= { tplinkProducts 254 }
	tplink-6500-24mpp4y-v1 OBJECT IDENTIFIER ::= { tplinkProducts 256 }
	tplink-sg2428lp		OBJECT IDENTIFIER ::= { tplinkProducts 258 }
	tplink-festa-fs308gp OBJECT IDENTIFIER ::= { tplinkProducts 260 }
	tplink-festa-fs310gp OBJECT IDENTIFIER ::= { tplinkProducts 262 }
	tplink-festa-fs318gp OBJECT IDENTIFIER ::= { tplinkProducts 264 }
	tplink-festa-fs328gp OBJECT IDENTIFIER ::= { tplinkProducts 266 }
	tplink-sg2428p-v530		OBJECT IDENTIFIER ::= { tplinkProducts 274 }
	tplink-s5500-24gp4f-v120	OBJECT IDENTIFIER ::= { tplinkProducts 276 }
	tplink-festa-fs308g OBJECT IDENTIFIER ::= { tplinkProducts 282 }
	tplink-sg2210mp-v5 OBJECT IDENTIFIER ::= { tplinkProducts 284 }
	tplink-s4500-8ghp2f-v2 OBJECT IDENTIFIER ::= { tplinkProducts 288 }
END
